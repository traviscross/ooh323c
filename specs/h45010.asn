Call-Offer-Operations
{
  itu-t recommendation h 450 10 version1(0) call-offer-operations(0)
}

DEFINITIONS AUTOMATIC TAGS ::=
BEGIN

  IMPORTS MixedExtension FROM Call-Hold-Operations
          {
            itu-t recommendation h 450 4 version1(0) call-hold-operations(0)
          }

          callWaiting FROM Call-Waiting-Operations
          {
            itu-t recommendation h 450 6 version1(0) call-waiting-operations(0)
          };

  H323CallOfferOperations ::= ENUMERATED
  {
    callOfferRequest(34),
    -- callWaiting(105), Imported from H.450.6
    remoteUserAlerting(115),
    cfbOverride(49)
  }

  CoReqOptArg ::= SEQUENCE
  {
    extension SEQUENCE SIZE (0..255) OF MixedExtension OPTIONAL,
    ...
  }

  RUAlertOptArg ::= SEQUENCE
  {
    extension SEQUENCE SIZE (0..255) OF MixedExtension OPTIONAL,
    ...
  }

  CfbOvrOptArg ::= SEQUENCE
  {
    extension SEQUENCE SIZE (0..255) OF MixedExtension OPTIONAL,
    ...
  }

END -- of Call-Offer-Operations
