Call-Hold-Operations
{
  itu-t recommendation h 450 4 version1(0)  call-hold-operations(0)
}

DEFINITIONS  AUTOMATIC TAGS  ::=
BEGIN

  IMPORTS EXTENSION, Extension FROM Manufacturer-specific-service-extension-definition
  {
    itu-t recommendation h 450 1 version1(0) msi-definition(18)
  }
 
  notAvailable,  invalidCallState,  resourceUnavailable,  supplementaryServiceInteractionNotAllowed FROM H4501-General-Error-List
  {
    itu-t recommendation h 450 1 version1(0) general-error-list (1)
  }
 
  NonStandardParameter FROM H323-MESSAGES;


  CallHoldOperation ::= ENUMERATED
  {
    holdNotific(101),
    retrieveNotific(102),
    remoteHold(103),
    remoteRetrieve(104)  
  }

  HoldNotificArg ::= SEQUENCE
  {
    extensionArg  SEQUENCE SIZE (0..255) OF MixedExtension OPTIONAL,
    ...
  }
        
  RetrieveNotificArg ::= SEQUENCE
  {
    extensionArg  SEQUENCE SIZE (0..255) OF MixedExtension OPTIONAL,
    ...
  }

  RemoteHoldArg ::= SEQUENCE
  {
    extensionArg SEQUENCE SIZE (0..255) OF MixedExtension OPTIONAL,
    ...
  }

  RemoteHoldRes ::= SEQUENCE
  {
    extensionRes SEQUENCE SIZE (0..255) OF MixedExtension OPTIONAL,
    ...
  }


  RemoteRetrieveArg  ::= SEQUENCE
  {
    extensionArg  SEQUENCE SIZE (0..255) OF MixedExtension OPTIONAL,
    ...
  }

  RemoteRetrieveRes  ::= SEQUENCE
  {
    extensionRes SEQUENCE SIZE (0..255) OF MixedExtension OPTIONAL,
    ...
  }

  MixedExtension ::= CHOICE
  {
    extension Extension,
    nonStandardData NonStandardParameter
  }

  Extension ::= SEQUENCE
  {
    extensionId OBJECT IDENTIFIER,
    argument OCTET STRING
  }

END     -- of Call-Hold-Operations
